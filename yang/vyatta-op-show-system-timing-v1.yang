module vyatta-op-show-system-timing-v1 {
	namespace "urn:vyatta.com:mgmt:vyatta-op-show-system-timing:1";
	prefix vyatta-op-show-system-timing-v1;

	import vyatta-opd-extensions-v1 {
		prefix opd;
	}
	import vyatta-op-show-v1 {
		prefix show;
	}
	import vyatta-system-timing-v1 {
		prefix timing;
	}
	import vyatta-op-show-system-v1 {
		prefix system;
	}

	organization "AT&T Inc.";
	contact
		"AT&T
		 Postal: 208 S. Akard Street
				 Dallas, TX 75202
		 Web: www.att.com";

	description
		"Copyright (c) 2021, AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Defines the top level 'timing' level under 'show system' for operational CLI";

	revision 2021-08-03 {
		description "Initial revision of version 1.";
	}

	opd:augment /show:show/system:system {
		opd:command timing {
			opd:help "Show system timing status";
			if-feature timing:timing;

			opd:command timing-source {
				opd:help "Show system timing source status";
				opd:on-enter "vyatta-show-timing-source";

				opd:command one-pps {
					opd:help "Show system 1PPS timing source status";
					opd:on-enter "vyatta-show-timing-source --one-pps";
				}
				opd:command frequency {
					opd:help "Show system frequency timing source status";
					opd:on-enter "vyatta-show-timing-source --frequency";
				}
			}
		}
	}
}
