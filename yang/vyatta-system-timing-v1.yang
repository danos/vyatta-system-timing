module vyatta-system-timing-v1 {
	namespace "urn:vyatta.com:mgmt:vyatta-system-timing:1";
	prefix vyatta-system-timing-v1;

	import vyatta-system-v1 {
		prefix system;
	}
	import configd-v1 {
		prefix configd;
	}
	organization "AT&T Inc.";
	contact
		"AT&T
		 Postal: 208 S. Akard Street
				 Dallas, TX 75202
		 Web: www.att.com";

	description
		"Copyright (c) 2021, AT&T Intellectual Property.
		All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		System Timing configuration";

	revision 2021-05-19 {
		description "Initial revision of version 1.";
	}

	feature timing {
		description "Vyatta system timing configuration support";
	}

	grouping source-status {
		leaf source {
			description "Current input source";
			type string;
		}
		leaf operating-status {
			description "Operating status of current input source";
			type string;
		}
		list priority {
			description "Priority list of the sources";
			key weighted-priority;
			leaf weighted-priority {
				description "Weighted priority, higher value indicates higher priority";
				type uint16 {
					range 1..100;
				}
			}
			leaf source {
				description "Input source";
				type string;
			}
		}
	}

	grouping system-timing {
		container timing {
			description "System timing configuration";
			configd:help "System timing configuration";
			if-feature timing;

			container timing-source {
				description "Timing source configuration";
				configd:help "Timing source configuration";

				container one-pps {
					description "1PPS source configuration";
					configd:help "1PPS source configuration";
					container gps-1pps {
						description "GPS-1PPS configuration";
						configd:help "GPS-1PPS configuration";
						leaf weighted-priority {
							description "Weighted priority";
							configd:help "Weighted priority";
							must "count(../../*/weighted-priority[. = current()]) = 1" {
								error-message "Duplicate priority";
							}
							type uint16 {
								range 1..100;
							}
						}
					}
					container ptp-1pps {
						description "PTP-1PPS configuration";
						configd:help "PTP-1PPS configuration";
						leaf weighted-priority {
							description "Weighted priority";
							configd:help "Weighted priority";
							must "count(../../*/weighted-priority[. = current()]) = 1" {
								error-message "Duplicate priority";
							}
							type uint16 {
								range 1..100;
							}
						}
					}
					container sma-1pps {
						description "SMA-1PPS configuration";
						configd:help "SMA-1PPS configuration";
						leaf weighted-priority {
							description "Weighted priority";
							configd:help "Weighted priority";
							must "count(../../*/weighted-priority[. = current()]) = 1" {
								error-message "Duplicate priority";
							}
							type uint16 {
								range 1..100;
							}
						}
					}
					container tod-1pps {
						description "ToD-1PPS configuration";
						configd:help "ToD-1PPS configuration";
						leaf weighted-priority {
							description "Weighted priority";
							configd:help "Weighted priority";
							must "count(../../*/weighted-priority[. = current()]) = 1" {
								error-message "Duplicate priority";
							}
							type uint16 {
								range 1..100;
							}
						}
					}
				}
				container frequency {
					description "Frequency source configuration";
					configd:help "Frequency source configuration";

					container gps {
						description "GPS frequency configuration";
						configd:help "GPS frequency configuration";
						leaf weighted-priority {
							description "Weighted priority";
							configd:help "Weighted priority";
							must "count(../../*/weighted-priority[. = current()]) = 1" {
								error-message "Duplicate priority";
							}
							type uint16 {
								range 1..100;
							}
						}
					}
					container synce {
						description "SyncE frequency configuration";
						configd:help "SyncE frequency configuration";
						leaf weighted-priority {
							description "Weighted priority";
							configd:help "Weighted priority";
							must "count(../../*/weighted-priority[. = current()]) = 1" {
								error-message "Duplicate priority";
							}
							type uint16 {
								range 1..100;
							}
						}
					}
					container ptp {
						description "PTP frequency configuration";
						configd:help "PTP frequency configuration";
						leaf weighted-priority {
							description "Weighted priority";
							configd:help "Weighted priority";
							must "count(../../*/weighted-priority[. = current()]) = 1" {
								error-message "Duplicate priority";
							}
							type uint16 {
								range 1..100;
							}
						}
					}
					container sma {
						description "SMA frequency configuration";
						configd:help "SMA frequency configuration";
						leaf weighted-priority {
							description "Weighted priority";
							configd:help "Weighted priority";
							must "count(../../*/weighted-priority[. = current()]) = 1" {
								error-message "Duplicate priority";
							}
							type uint16 {
								range 1..100;
							}
						}
					}
					container bits {
						description "BITS frequency configuration";
						configd:help "BITS frequency configuration";
						leaf weighted-priority {
							description "Weighted priority";
							configd:help "Weighted priority";
							must "count(../../*/weighted-priority[. = current()]) = 1" {
								error-message "Duplicate priority";
							}
							type uint16 {
								range 1..100;
							}
						}
					}
				}
			}
			leaf tod-output {
				description "Output of ToD (Time of Day) RJ45 interface";
				configd:help "Output of ToD (Time of Day) RJ45 interface";
				type boolean;
				default "false";
			}
			container timing-status {
				description "System timing status";
				config false;

				container timing-source {
					description "System timing-source state";

					container frequency-status {
						description "Frequency source status";
						uses source-status;
					}
					container one-pps-status {
						description "1PPS source status";
						uses source-status;
					}
				}
			}
		}
	}
	
	augment /system:system {
		uses system-timing;
	}
}
